# Python macro for PrintPupper
# Auto export .stl mesh to 3d print parts from freeCAD file

print('Macro start')

import FreeCAD
import Mesh

docfile = 'PrintPupper_v01_0'
outpath = './export/'

bodylabel_exname_list = [
    ['ppll_L',   '01_lower_leg_Left_2pcs'],
    ['ppll_R',   '02_lower_leg_Right_2pcs'],
    ['ppup',     '03_upper_leg_4pcs'],
    ['ppkl',     '04_knee_linkage_4pcs'],
    ['ppkn',     '05_knee_horn_4pcs'],
    ['ppcxout',  '06_coxa_outer_4pcs'],
    ['ppcxin_F', '07_coxa_innter_Front_2pcs'],
    ['ppcxin_B', '08_coxa_innter_Back_2pcs'],
    ['ppct',     '09_torso_center_1pcs'],
    ['ppft',     '10_torso_frontback_2pcs'],
    ['pppcbbox', '11_pcb_box_1pcs'],
    ['pplid',    '12_pcb_box_lid_1pcs'],
    ['ppbath',   '13_battery_holder_2pcs']
]

print('export from ', docfile)
for bodylabel_exname in bodylabel_exname_list:
    bodylabel = bodylabel_exname[0]
    exname = bodylabel_exname[1]
    expath = outpath + exname + '.stl'
    print('[', bodylabel, '] -> ', expath)
    objs=[]
    objs.append(FreeCAD.getDocument(docfile).getObjectsByLabel(bodylabel)[0])
    Mesh.export(objs, expath)
    del objs

print('Macro done')
